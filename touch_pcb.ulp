#usage "<qt><nobr>This ULP calculates and place a rotary capacitive sensor.<p>"
       "<author>Author: Dan Afonso <dafonso@afonsoconsulting.com>, </author></nobr></qt>";
// THIS PROGRAM IS PROVIDED AS IS AND WITHOUT WARRANTY OF ANY KIND,
// EXPRESSED OR IMPLIED.
//Globals
string solderpoint      = "";
string file;
string s;  //temporary string
int c; // temporary counter
// Basic parameters
real outerRadius        = 15.0;
real innerRadius        = 6.0;
int numSegments = 3;
real armsLength = 2;
real anglePerSegment = 2*PI/real(numSegments);
real gap = (10.0/180.0)*PI;

real lastAngle = 0;
real lastRadius = 0;

real rad2deg            = 360/(2*PI);
// Converts from radial coordinates to Cartesian. This returns the X portion
real r2c_x(real r, real a, real o){
    return (r*cos(a)) + (o*sin(a));
}
// Converts from radial coordinates to Cartesian. This returns the Y portion
real r2c_y(real r, real a, real o){
    return (r*sin(a)) - (o*cos(a));
}

real xPos(real r, int segment, real offset, real compensation) {
    real angle = (anglePerSegment * real(segment)) + (offset * compensation);
    angle -= 90.0/180.0 * PI;

     if (angle > 2*PI)
    {
        angle -= 2*PI;
    }
    if (angle < 0)
    {
        angle += 2*PI;
    }

    real x = cos(angle) * (r);
    return x;
}

real yPos(real r, int segment, real offset, real compensation) {
    real angle = (anglePerSegment * real(segment)) + (offset * compensation);
    angle -= 90.0/180.0 * PI;

     if (angle > 2*PI)
    {
        angle -= 2*PI;
    }
    if (angle < 0)
    {
        angle += 2*PI;
    }

    real y = sin(angle) * (r);
    return y;
}

real xP(real r, real angle, real comp) {    

    if (comp != 0)
    {
        real value = (r-17.0) / r;
        comp = (comp) * value;
    }

    angle += comp;    

    angle = angle / 180.0 * PI;    

    angle -= 90.0/180.0 * PI;

    if (angle > 2*PI)
    {
        angle -= 2*PI;
    }
    if (angle < 0)
    {
        angle += 2*PI;
    }    

    real x = cos(angle) * (r);
    return x;
}

real yP(real r, real angle, real comp) {
    if (comp != 0)
    {
        real value = (r-17.0) / r;
        comp = comp * value;
    }

    angle += comp;    

    angle = angle / 180.0 * PI;    

    angle -= 90.0/180.0 * PI;

    if (angle > 2*PI)
    {
        angle -= 2*PI;
    }
    if (angle < 0)
    {
        angle += 2*PI;
    }

    real y = sin(angle) * (r);
    return y;
}

real curve(real angle)
{
    return angle;
}

void doIt(void){

    string cmd = "CHANGE LAYER 20; CHANGE WIDTH .1;SET WIRE_BEND 2;\n";
    sprintf(s, "CIRCLE (0 0) (%.4f 0);\n", innerRadius-1);
    cmd += s;

    real r1 = outerRadius + 2;
    real r2 = outerRadius + 2 + armsLength;
    real r12 = outerRadius + 5;

    sprintf(s,"WIRE (%.4f %.4f) +%.4f (%.4f %.4f);",xP(r1,10.0,0),yP(r1,10.0,0),curve(30.0),xP(r1,30.0,0),yP(r1,30.0,0));
    cmd += s;

    sprintf(s,"WIRE (%.4f %.4f) (%.4f %.4f);",xP(r1,30.0,0),yP(r1,30.0,0),xP(r12-1,30.0,15.0),yP(r12-1,30.0,15.0));
    cmd += s;

    sprintf(s,"WIRE (%.4f %.4f) +%.4f (%.4f %.4f);",xP(r12-1,30.0,15.0),yP(r12-1,30.0,15.0),curve(90.0),xP(r12,33.0,15.0),yP(r12,33.0,15.0));
    cmd += s;    

    sprintf(s,"WIRE (%.4f %.4f) (%.4f %.4f);",xP(r12,33.0,15.0),yP(r12,33.0,15.0),xP(r12,57.0,-15.0),yP(r12,57.0,-15.0));
    cmd += s;

    sprintf(s,"WIRE (%.4f %.4f) +%.4f (%.4f %.4f);",xP(r12,57.0,-15.0),yP(r12,57.0,-15.0),curve(90.0),xP(r12-1,60.0,-15.0),yP(r12-1,60.0,-15.0));
    cmd += s;

    sprintf(s,"WIRE (%.4f %.4f) (%.4f %.4f);",xP(r12-1,60.0,-15.0),yP(r12-1,60.0,-15.0),xP(r1,60.0,0),yP(r1,60.0,0));
    cmd += s;

    //First Mouting Hole
    sprintf(s,"WIRE (%.4f %.4f) +%.4f (%.4f %.4f);",xP(r1,60.0,0),yP(r1,60.0,0),curve(40.0),xP(r1,110.0,0),yP(r1,110.0,0));
    cmd += s;

    sprintf(s,"WIRE (%.4f %.4f) (%.4f %.4f);",xP(r1,110.0,0),yP(r1,110,0),xP(r2,110.0,10.0),yP(r2,110.0,10.0));
    cmd += s;

    sprintf(s,"WIRE (%.4f %.4f) +%.4f (%.4f %.4f);",xP(r2,110.0,10.0),yP(r2,110.0,10.0),curve(180.0),xP(r2,130.0,-10.0),yP(r2,130.0,-10.0));
    cmd += s;

    sprintf(s,"WIRE (%.4f %.4f) (%.4f %.4f);",xP(r2,130.0,-10.0),yP(r2,130.0,-10.0),xP(r1,130.0,0),yP(r1,130.0,0));
    cmd += s;

    //Second Mouting Hole
    sprintf(s,"WIRE (%.4f %.4f) +%.4f (%.4f %.4f);",xP(r1,130.0,0),yP(r1,130.0,0),curve(100.0),xP(r1,230.0,0),yP(r1,230.0,0));
    cmd += s;

    sprintf(s,"WIRE (%.4f %.4f) (%.4f %.4f);",xP(r1,230.0,0),yP(r1,230,0),xP(r2,230.0,10.0),yP(r2,230.0,10.0));
    cmd += s;

    sprintf(s,"WIRE (%.4f %.4f) +%.4f (%.4f %.4f);",xP(r2,230.0,10.0),yP(r2,230.0,10.0),curve(180.0),xP(r2,250.0,-10.0),yP(r2,250.0,-10.0));
    cmd += s;

    sprintf(s,"WIRE (%.4f %.4f) (%.4f %.4f);",xP(r2,250.0,-10.0),yP(r2,250.0,-10.0),xP(r1,250.0,0),yP(r1,250.0,0));
    cmd += s;

    //Third Mouting Hole
    sprintf(s,"WIRE (%.4f %.4f) +%.4f (%.4f %.4f);",xP(r1,250.0,0),yP(r1,250.0,0),curve(100.0),xP(r1,350.0,0),yP(r1,350.0,0));
    cmd += s;

    sprintf(s,"WIRE (%.4f %.4f) (%.4f %.4f);",xP(r1,350.0,0),yP(r1,350,0),xP(r2,350.0,10.0),yP(r2,350.0,10.0));
    cmd += s;

    sprintf(s,"WIRE (%.4f %.4f) +%.4f (%.4f %.4f);",xP(r2,350.0,10.0),yP(r2,350.0,10.0),curve(180.0),xP(r2,10.0,-10.0),yP(r2,10.0,-10.0));
    cmd += s;

    sprintf(s,"WIRE (%.4f %.4f) (%.4f %.4f);",xP(r2,10.0,-10.0),yP(r2,10.0,-10.0),xP(r1,10.0,0),yP(r1,10.0,0));
    cmd += s;

    //Mounting holes
    sprintf(s,"HOLE 2 (%.4f %.4f);",xPos(outerRadius+1+3,1,0,1),yPos(outerRadius+1+3,1,0,1));
    cmd += s;

    sprintf(s,"HOLE 2 (%.4f %.4f);",xPos(outerRadius+1+3,2,0,1),yPos(outerRadius+1+3,2,0,1));
    cmd += s;

    sprintf(s,"HOLE 2 (%.4f %.4f);",xPos(outerRadius+1+3,0,0,1),yPos(outerRadius+1+3,0,0,1));
    cmd += s;    

    // Finish up
    output(file, "wtD") printf("%s", cmd);
    sprintf(cmd, "SCRIPT '%s';", file);
    exit (cmd);
}

// The actual work.
void doIt2(void){

    string cmd = "CHANGE LAYER 20; CHANGE WIDTH .1;SET WIRE_BEND 2;\n";
    sprintf(s, "CIRCLE (0 0) (%.4f 0);\n", innerRadius-1);
    cmd += s;

    for (int i=0;i<numSegments;i++)
    {
        real compensation = (outerRadius+2.0)/(outerRadius+armsLength+1.0);

        real x = 0;
        real y = 0;
        if (i == numSegments-1)
        {
            x = xPos(outerRadius+2,i,gap,1.0);
            y = yPos(outerRadius+2,i,gap,1.0);
            
            gap = gap * 1.5;            
        }
        else if (i == 0)
        {
            x = xPos(outerRadius+2,i,gap*1.5,1.0);
            y = yPos(outerRadius+2,i,gap*1.5,1.0);
        }
        else
        {
            x = xPos(outerRadius+2,i,gap,1.0);
            y = yPos(outerRadius+2,i,gap,1.0);
        }
        
        real x1 = xPos(outerRadius+2,i+1,-gap,1.0);
        real y1 = yPos(outerRadius+2,i+1,-gap,1.0);

        real x2 = xPos(outerRadius+armsLength+1,i+1,-gap,compensation);
        real y2 = yPos(outerRadius+armsLength+1,i+1,-gap,compensation);        

        real x3 = xPos(outerRadius+armsLength+1,i+1,gap,compensation);
        real y3 = yPos(outerRadius+armsLength+1,i+1,gap,compensation);

        real x4 = xPos(outerRadius+2,i+1,gap,1.0);
        real y4 = yPos(outerRadius+2,i+1,gap,1.0);

        //Curved Segment Start
        sprintf(s,"WIRE (%.4f %.4f) +%.4f (%.4f %.4f);",x,y,(anglePerSegment-(2*gap))*180/PI,x1,y1);
        cmd += s;

        //Left Arm
        sprintf(s,"WIRE (%.4f %.4f) (%.4f %.4f);",x1,y1,x2,y2);
        cmd += s;

        //Right Arm
        sprintf(s,"WIRE (%.4f %.4f) +%.4f (%.4f %.4f);",x2,y2,gap*180/PI,x3,y3);
        cmd += s;        

        //Top Arm        
        sprintf(s,"WIRE (%.4f %.4f) (%.4f %.4f);",x3,y3,x4,y4);
        cmd += s;
    }

    //Mounting holes
    sprintf(s,"HOLE 2 (%.4f %.4f);",xPos(outerRadius+1+(armsLength/2),1,0,1),yPos(outerRadius+1+(armsLength/2),1,0,1));
    cmd += s;

    sprintf(s,"HOLE 2 (%.4f %.4f);",xPos(outerRadius+1+(armsLength/2),2,0,1),yPos(outerRadius+1+(armsLength/2),2,0,1));
    cmd += s;

    sprintf(s,"HOLE 2 (%.4f %.4f);",xPos(outerRadius+1+(armsLength/2),0,0,1),yPos(outerRadius+1+(armsLength/2),0,0,1));
    cmd += s;


    // Finish up
    output(file, "wtD") printf("%s", cmd);
    sprintf(cmd, "SCRIPT '%s';", file);
    exit (cmd);
}
// *** main ***
// Setup
if (board) {
  board(B) file = filesetext(B.name, ".scr");
  solderpoint = ";\nVIA ";
}
else if (package) {
  library(L) file = filesetext(L.name, ".scr");
  solderpoint = ";\nPAD ";
}
else {
  dlgMessageBox("Start this ULP in a Board- or Package-Editor!", "OK");
  exit(0);
}
// Dialog
real bandMinimum        = 5.0;
/*
real bandMaximum        = 8.0;
int channels            = 3;
real channelGap            = .1;
int debug                = 1;
*/
dlgDialog(filename(argv[0])) {
    dlgVBoxLayout {
        dlgLabel("<nobr> All measures in <b>mm</b> </nobr>");
        dlgGridLayout {
            dlgCell(0,0) dlgLabel("Outer Raidus");
            dlgCell(0,1) dlgRealEdit(outerRadius, 10.0, 100.0);
            dlgCell(1,0) dlgLabel("Inner Raidus");
            dlgCell(1,1) dlgRealEdit(innerRadius, 5.0, 30.0);
        }
    }
    dlgHBoxLayout {
        dlgPushButton("OK") {
            int ok = 1;

            if (innerRadius > (outerRadius - bandMinimum)){
                ok = 0;
                sprintf(s, "<qt>Inner Radius is too large");
                dlgMessageBox(s, "OK");
            }
            if (ok) {
                dlgAccept();
                doIt();
            }
        }
    }
};
